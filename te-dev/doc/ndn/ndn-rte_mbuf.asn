-- SPDX-License-Identifier: Apache-2.0

TE-NDN-RTE_mbuf
DEFINITIONS ::=
BEGIN

IMPORTS DATA-UNIT FROM TE-NDN-General;

EXPORTS RTE_mbuf-CSAP;

RTE_mbuf-CSAP ::= IMPLICIT SEQUENCE {
    pkt-ring        [0] DATA-UNIT{UniversalString},
    pkt-pool        [1] DATA-UNIT{UniversalString}
}

END

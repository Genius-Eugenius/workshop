-- SPDX-License-Identifier: Apache-2.0

TE-NDN-Dummy
DEFINITIONS ::=
BEGIN

IMPORTS DATA-UNIT FROM TE-NDN-General;

EXPORTS File-Message, File-CSAP;


File-Message ::= IMPLICIT SEQUENCE {
    line        DATA-UNIT{UniversalString},
}

File-CSAP ::= IMPLICIT SEQUENCE {
    filename    DATA-UNIT{UniversalString},
    mode        DATA-UNIT{UniversalString} OPTIONAL
}

END

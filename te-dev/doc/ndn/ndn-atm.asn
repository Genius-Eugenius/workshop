-- SPDX-License-Identifier: Apache-2.0

TE-NDN-ATM
DEFINITIONS ::=
BEGIN

IMPORTS DATA-UNIT FROM TE-NDN-General;

EXPORTS ATM-UNI-Header, ATM-NNI-Header, ATM-CSAP,
        CPCS-PDU-Trailer, AAL5-CSAP;


ATM-UNI-Header ::= SEQUENCE {
    gfc             DATA-UNIT{INTEGER (0..15)} OPTIONAL,
    vpi             DATA-UNIT{INTEGER (0..255)} OPTIONAL,
    vci             DATA-UNIT{INTEGER (0..65535)} OPTIONAL,
    payload-type    DATA-UNIT{INTEGER (0..7)} OPTIONAL,
    clp             DATA-UNIT{INTEGER {0, 1}} OPTIONAL,
    hec             DATA-UNIT{INTEGER (0..255)} OPTIONAL
}

ATM-NNI-Header ::= SEQUENCE {
    vpi             DATA-UNIT{INTEGER (0..4095)} OPTIONAL,
    vci             DATA-UNIT{INTEGER (0..65535)} OPTIONAL,
    payload-type    DATA-UNIT{INTEGER (0..7)} OPTIONAL,
    clp             DATA-UNIT{INTEGER {0, 1}} OPTIONAL,
    hec             DATA-UNIT{INTEGER (0..255)} OPTIONAL
}

ATM-Coding-Scheme ::= INTEGER {
    uni(0),
    nni(1)
}

ATM-CSAP ::= SEQUENCE {
    device-id       DATA-UNIT{UniversalString} OPTIONAL,
    type            ATM-Coding-Scheme,
    vpi             DATA-UNIT{INTEGER (0..4095)} OPTIONAL,
    vci             DATA-UNIT{INTEGER (0..65535)} OPTIONAL,
    congestion      DATA-UNIT{INTEGER (0, 1)} OPTIONAL,
    clp             DATA-UNIT{INTEGER {0, 1}} OPTIONAL,
}


CPCS-PDU-Trailer ::= SEQUENCE {
    cpcs-uu         DATA-UNIT{INTEGER (0..255)} OPTIONAL,
    cpi             DATA-UNIT{INTEGER (0..255)} OPTIONAL,
    length          DATA-UNIT{INTEGER (0..65535)} OPTIONAL,
    crc             DATA-UNIT{INTEGER (0..4294967295)} OPTIONAL
}

AAL5-CSAP ::=  SEQUENCE {
    cpcs-uu         DATA-UNIT{INTEGER (0..255)} OPTIONAL,
    cpi             DATA-UNIT{INTEGER (0..255)} OPTIONAL,

    encap          CHOICE {
        vcMultiplexRoutedProtocol   NULL,
        llc SEQUENCE {
            // FIXME
            ether-type  DATA-UNIT{INTEGER (0..65535)} OPTIONAL
        }
    } OPTIONAL
}

END
